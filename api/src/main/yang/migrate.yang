// Contents of "migrate"
module migrate {
    namespace "urn:opendaylight:migrate";
    prefix "migrate";
    import ietf-inet-types { prefix "inet"; revision-date 2013-07-15; }
    import controllers { prefix controllers; revision-date 2018-11-25; }
    revision 2019-07-26 {
        description "Initial revision";
    }

    rpc migrate-abnormal-controller {
        input {
            leaf controller-ip {
                type inet:ipv4-address;
            }
        }
        output {
            leaf target-ip {
                type string;
            }
            uses controllers:controller-types;
        }
    }
}
