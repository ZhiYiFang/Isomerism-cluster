// Contents of "controllers"
module controllers {
    namespace "urn:opendaylight:controllers";
    prefix "controllers";
    import ietf-yang-types { prefix "yang"; revision-date 2013-07-15; }
    import guard { prefix guard; revision-date 2015-01-05; }
    import ietf-inet-types { prefix "inet"; revision-date 2013-07-15; }
    revision 2018-11-25 {
        description "Initial revision";
    }

    grouping user-info {
        description "控制器对应的登录名";
        leaf name {
            type string;
        }
        leaf password {
            type string;
        }
        leaf domain {
            type string;
        }
        leaf token {
            type string;
        }
    }
    grouping controller-types {
        leaf type-name {
            type enumeration {
                enum "vcf" {
                    value 0;
                    description "vcf 控制器";
                }
                enum "agile" {
                    value 1;
                    description "agile 控制器";
                }
                enum "apic" {
                    value 2;
                    description "apic 控制器";
                }
                enum "floodlight" {
                    value 3;
                    description "floodlight controller";
                }
                enum "ryu" {
                    value 4;
                    description "ryu controller";
                }
                enum "opendaylight" {
                    value 5;
                    description "opendaylight controller";
                }
            }
        }
    }

    container basic-setting {
        container server-url {
            leaf server-setting-url {
                type string;
            }
        }
        container attack-confirm-url {
            leaf attack-confirm-setting-url {
                type string;
            }
        }
        leaf middle-ip {
            type inet:ipv4-address;
        }
        container redis-setting {
            leaf ip {
                type inet:ipv4-address;
            }

            leaf port {
                type inet:port-number;
            }
        }
        container mininet-setting {
            leaf user-ip {
                type string;
            }
        }
    }

    container isomerism {
        list isomerism-controllers {
            key ip;
            leaf midlle-ware {
                type inet:ipv4-address;
                description "所属中间件的ip地址";
            }
            uses controller-types;
            leaf ip {
                type inet:ipv4-address;
            }
            leaf port {
                type inet:port-number;
            }
            container user {
                uses user-info;
            }
            leaf controller-status {
                default "up";
                type enumeration {
                    enum "up" {
                        value 0;
                        description "控制器正常";
                    }
                    enum "down" {
                        value 1;
                        description "控制器宕机";
                    }
                    enum "abnormal" {
                        value 2;
                        description "异常控制器";
                    }
                }
            }
        }
    }

    grouping alert-common {
        leaf alert-no {
            type int32;
        }

        leaf message-type {
            type enumeration {
                enum "Alert" {
                    value 0;
                }
                enum "Calculate" {
                    value 1;
                }
                enum "Action" {
                    value 2;
                }
                enum "Test" {
                    value 3;
                }
                enum "Normal" {
                    value 4;
                }
            }
        }
        leaf message-level {
            description "警报等级";
            type enumeration {
                enum "low" {
                    value 0;
                }
                enum "medium" {
                    value 1;
                }
                enum "high" {
                    value 2;
                }
            }
        }
        leaf message-desc {
            type string;
        }

        leaf message-time {
            type string;
        }
        leaf source-type {
            description "组件类型";
            type enumeration {
                enum "isomerism" {
                    value 0;
                }
                enum "virtualization" {
                    value 1;
                }
                enum "transformer" {
                    value 2;
                }
            }
        }
        leaf source-ip {
            type inet:ipv4-address;
        }
    }

    // 三大中间件发出的警告消息
    container alert-message {
        list alert-messages {
            uses alert-common;
        }
    }

    // 数据平面的公有数据
    container data-plane-link {
        list data-plane-links {
            leaf src-switch {
                type string;
            }
            leaf src-port {
                type string;
            }
            leaf dst-switch {
                type string;
            }
            leaf dst-port {
                type string;
            }
            leaf is-bidirectional {
                type boolean;
            }
        }

        list sw-to-controller{
            leaf sw-id {
                type string;
            }
            leaf controller-ip {
                type string;
            }
        }
    }

    rpc get-all-switches {
        output {
            list switches {
                // 后边会根据情况添加端口、版本号等其他各种信息
                leaf dpid {
                    type guard:datapath-id;
                }

                // 暂时直接吧json返回回来
                leaf port {
                    type string;
                }
                leaf port-desc {
                    type string;
                }
            }
        }
    }

    rpc get-switch-flow-table {
        input {
            leaf dpid {
                type guard:datapath-id;
            }
        }
        output {
            leaf result {
                type string;
            }
        }
    }

    rpc send-alert {
        input {
            uses alert-common;
            leaf abnormal-controller-ip{
            	type string;
            }
        }
        output {
            leaf result {
                type boolean;
            }
        }
    }
    grouping flow-basic {

    	leaf flow-name{
    		type string;
    	}
    	
        leaf table-id {
            type int32;
        }

        leaf priority {
            type int32;
        }

        leaf idle-timeout {
            type int32;
        }

        leaf hard-timeout {
            type int32;
        }

        leaf flow-mod-cmd {
            type enumeration {
                enum "add" {
                    description "增加流表";
                    value 0;
                }
                enum "modify" {
                    description "修改流表";
                    value 1;
                }
                enum "delete" {
                    description "删除流表";
                    value 2;
                }
            }
        }
    }

    grouping match-items {

        leaf eth-src {
            type yang:mac-address;
        }
        leaf eth-dst {
            type yang:mac-address;
        }
        leaf ipv4-src {
            type inet:ipv4-address;
        }
        leaf ipv4-dst {
            type inet:ipv4-address;
        }
        leaf src-port {
            type inet:port-number;
        }
        leaf dst-port {
            type inet:port-number;
        }
    }
    grouping instruction {
        //        choice instruction {
        //            case write-actions {
        //                leaf out-put {
        //                    type string;
        //                }
        //            }
        //        }
        leaf out-put-port {
            type string;
        }
    }
    rpc flow-mod {
        input {
            leaf dpid {
                type guard:datapath-id;
            }
            container flow-input {
                uses flow-basic;
                container matches {
                    uses match-items;
                }
                leaf out-put-port {
                    type string;
                }
            }
        }
        output {
            leaf result {
                type string;
            }
        }
    }
    notification controller-down {
        description "有异构控制器宕机";
        container down-controller {
            leaf ip {
                type inet:ipv4-address;
            }
            uses controller-types;
        }
        container new-controller {
            leaf ip {
                type inet:ipv4-address;
            }
            uses controller-types;
        }
    }
}
