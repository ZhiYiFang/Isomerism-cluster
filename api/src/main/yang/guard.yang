module guard {
    yang-version 1;
    namespace "urn:opendaylight:params:xml:ns:yang:guard";
    prefix "guard";
    import ietf-inet-types { prefix "inet"; revision-date 2013-07-15; }

    revision "2015-01-05" {
        description "Initial revision of guard model";
    }
    grouping ip-port{
    	leaf ip{
    		type inet:ipv4-address;
    	}
    	leaf port{
    		type inet:port-number;
    	}
    }
    typedef datapath-id {
        type string {
          pattern
            '[0-9a-fA-F]{2}(:[0-9a-fA-F]{2}){7}';
        }
        description
          "The datapath-d type represents OpenFlow datapath-id .
        The canonical representation uses lowercase characters.

        In the value set and its semantics, this type is similar
        to the MacAddress textual convention of the SMIv2, but with
        16 extra bits";
        reference
          "Openflow 1.3.0 Spec
           IEEE 802: IEEE Standard for Local and Metropolitan Area
                Networks: Overview and Architecture
           RFC 2579: Textual Conventions for SMIv2";
    }
    
    rpc hello{
    	input{
    		leaf name{
    		    type string;
    		}
    	}
    	output{
    		leaf result{
    			type string;
    		}
    	}
    }
}
