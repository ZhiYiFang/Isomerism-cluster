// Contents of "floodlightflowtable"
module floodlightflowtable {
    namespace "urn:opendaylight:floodlightflowtable";
    prefix "floodlightflowtable";
    import guard { prefix guard; revision-date 2015-01-05; }

    revision 2019-06-02 {
        description "Initial revision";
    }

    rpc get-floodlight-switch-flowtable{
    	input{
    		uses guard:ip-port;
    		leaf dpid{
    			type guard:datapath-id;
    		}
    	}
    	output{
    		leaf result{
    			type string;
    		}
    	}
    }
}
